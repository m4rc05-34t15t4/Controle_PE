FME workspace MI_ligacao_FME-2020 (backup).fmw

Parameters:
- SourceDataset_POSTGIS = Controle_PE   # Database
- FEATURE_TYPES = public.edicao
- DestDataset_POSTGIS = Controle_PE   # Database
- SourceDataset_POSTGIS_2 = MOLDURAS_EDGV_BAHIA_23S   # Database
- FEATURE_TYPES_2 = public.aux_moldura_a
- SourceDataset_POSTGIS_5 = MOLDURAS_EDGV_BAHIA_24S   # Database
- FEATURE_TYPES_3 = public.aux_moldura_a

Readers:
- POSTGIS_1: POSTGIS from $(SourceDataset_POSTGIS) in EPSG:4674
- POSTGIS_3: POSTGIS from $(SourceDataset_POSTGIS_2)
- POSTGIS_4: POSTGIS from $(SourceDataset_POSTGIS_5)

Writers:
- POSTGIS_2: POSTGIS to $(DestDataset_POSTGIS) in EPSG:4674

Note: : Controle_PE [POSTGIS] EDICAO
edicao (reader POSTGIS_1)
    attributes: id int8,PrimaryKey, mi varchar(80), bloco varchar(80), status varchar(80), editor varchar(80), inicioedicao varchar(80), terminoedicao varchar(80), revisor1 varchar(80), inicio1rev varchar(80), termino1rev varchar(80), servidor varchar(80), niveis varchar(200), densidade varchar(200), revisor2 varchar(80), inicio2rev varchar(80), termino2rev varchar(80), nome_carta varchar(80), inom text, iniciocorrecao1 varchar(80), terminocorrecao1 varchar(80), iniciocorrecao2 varchar(80), terminocorrecao2 varchar(80), impressa bool, ligacao bool, totalobj varchar(200), total_p numeric(20,0), total_l numeric(20,0), total_a numeric(20,0), txt_p numeric(20,0), txt_l varchar(200),
      o varchar(80), s varchar(80), se varchar(80), so varchar(80), l varchar(80), n varchar(80), no varchar(80), ne varchar(80), linha int2, coluna int2, regiao text
    -> AttributeCreator
AttributeCreator
    ATTR_TABLE:
      SET_TO _escala = FME_CONDITIONAL:DEFAULT_VALUE'_FME_NO_OP_'BOOL_OP;OR;COMPOSITE_TEST;1;TEST @StringLength(@Value(mi)) >= 9'25K'BOOL_OP;OR;COMPOSITE_TEST;1;TEST @StringLength(@Value(mi)) >= 7'50K'BOOL_OP;OR;COMPOSITE_TEST;1;TEST @StringLength(@Value(mi)) >= 4'100K'FME_NUM_CONDITIONS4___
      SET_TO _lado = @mult(@Length(),0.25)
    -> AttributeKeeper
AttributeKeeper
    KEEP_ATTRS = _escala,_lado,mi
    -> CenterPointReplacer
    -> MI
MI: Inspector
CenterPointReplacer
    POINTTYPE = CENTER
    POINT -> NO
    POINT -> O
    POINT -> SO
    POINT -> Junction
NO: Offsetter
    MODE = Cartesian Coordinate
    XOFF = -@Value(_lado)
    YOFF = @Value(_lado)
    ZOFF = 0
    OFFSET -> AttributeCreator_2
AttributeCreator_2
    ATTR_TABLE = SET_TO _funcao = NO
    -> Junction_4
O: Offsetter
    MODE = Cartesian Coordinate
    XOFF = -@Value(_lado)
    YOFF = 0
    ZOFF = 0
    OFFSET -> AttributeCreator_3
AttributeCreator_3
    ATTR_TABLE = SET_TO _funcao = O
    -> Junction_4
Junction
    -> N
    -> S
    -> NE
    -> E
    -> SE
N: Offsetter
    MODE = Cartesian Coordinate
    XOFF = 0
    YOFF = @Value(_lado)
    ZOFF = 0
    OFFSET -> AttributeCreator_5
AttributeCreator_5
    ATTR_TABLE = SET_TO _funcao = N
    -> Junction_3
NE: Offsetter
    MODE = Cartesian Coordinate
    XOFF = @Value(_lado)
    YOFF = @Value(_lado)
    ZOFF = 0
    OFFSET -> AttributeCreator_8
AttributeCreator_8
    ATTR_TABLE = SET_TO _funcao = NE
    -> Junction_2
E: Offsetter
    MODE = Cartesian Coordinate
    XOFF = @Value(_lado)
    YOFF = 0
    ZOFF = 0
    OFFSET -> AttributeCreator_9
AttributeCreator_9
    ATTR_TABLE = SET_TO _funcao = E
    -> Junction_2
SE: Offsetter
    MODE = Cartesian Coordinate
    XOFF = @Value(_lado)
    YOFF = -@Value(_lado)
    ZOFF = 0
    OFFSET -> AttributeCreator_10
AttributeCreator_10
    ATTR_TABLE = SET_TO _funcao = SE
    -> Junction_2
S: Offsetter
    MODE = Cartesian Coordinate
    XOFF = 0
    YOFF = -@Value(_lado)
    ZOFF = 0
    OFFSET -> AttributeCreator_7
AttributeCreator_7
    ATTR_TABLE = SET_TO _funcao = S
    -> Junction_3
SO: Offsetter
    MODE = Cartesian Coordinate
    XOFF = -@Value(_lado)
    YOFF = -@Value(_lado)
    ZOFF = 0
    OFFSET -> AttributeCreator_4
AttributeCreator_4
    ATTR_TABLE = SET_TO _funcao = SO
    -> Junction_4
Junction_4
    -> Junction_3
Junction_3
    -> Junction_2
Junction_2
    -> PointOnAreaOverlayer [POINT]
Note: : MOLDURAS_EDGV_BAHIA_23S [POSTGIS]
aux_moldura_a (reader POSTGIS_3)
    attributes: id serial, mi varchar(80), inom varchar(80), escala varchar(80), nomecarta varchar(80), anoaquisicao varchar(80), engrespaquisicao varchar(80), opaquisicao varchar(80), datainicioaquisicao date, datafimaquisicao date, engresprevisaoaquisicao varchar(80), oprevisaoaquisicao varchar(80), datainiciorevaquisicao date, datafimrevaquisicao date, engrespreambulacao varchar(80), opreambulacao varchar(80), datainicioreambulacao date, datafimreambulacao date, oprevisaoreambulacao varchar(80), engrespvalidacaoedicao varchar(80), opvalidacao varchar(80), datainiciovalidacao date, datafimvalidacao date, opedicao1 varchar(80), datainicioedicao1 date, datafimedicao1 date, oprevedicao1 varchar(80), datainiciorevedicao1 date, datafimrevedicao1 date, opedicao2 varchar(80),
      datainicioedicao2 date, datafimedicao2 date
    -> Reprojector
Note: : MOLDURAS_EDGV_BAHIA_24S [POSTGIS]
aux_moldura_a (reader POSTGIS_4)
    attributes: id serial, mi varchar(80), inom varchar(80), escala varchar(80), nomecarta varchar(80), anoaquisicao varchar(80), engrespaquisicao varchar(80), opaquisicao varchar(80), datainicioaquisicao date, datafimaquisicao date, engresprevisaoaquisicao varchar(80), oprevisaoaquisicao varchar(80), datainiciorevaquisicao date, datafimrevaquisicao date, engrespreambulacao varchar(80), opreambulacao varchar(80), datainicioreambulacao date, datafimreambulacao date, oprevisaoreambulacao varchar(80), engrespvalidacaoedicao varchar(80), opvalidacao varchar(80), datainiciovalidacao date, datafimvalidacao date, opedicao1 varchar(80), datainicioedicao1 date, datafimedicao1 date, oprevedicao1 varchar(80), datainiciorevedicao1 date, datafimrevedicao1 date, opedicao2 varchar(80),
      datainicioedicao2 date, datafimedicao2 date
    -> Reprojector
Reprojector
    DEST = EPSG:4674
    INTERPOLATION_TYPE_NAME = Nearest Neighbor
    RASTER_CELL_SIZE = Preserve Cells
    RASTER_TOLERANCE = 0.0
    SOURCE = Read from feature
    REPROJECTED -> AttributeKeeper_3
AttributeKeeper_3
    KEEP_ATTRS = mi
    -> PointOnAreaOverlayer [AREA]
PointOnAreaOverlayer
    ATTR_ACCUM_MODE = Prefix Incoming
    DEAGGREGATE_INPUT = Yes
    INCOMING_PREFIX = LIG_
    OV_ATTR = _overlaps
    POLYS_FIRST = NO
    POINT -> AttributeFilter
AttributeFilter
    ATTR_NAME = _funcao
    ATTR_VALUES = <Empty>,<Missing>,<Null>,<Unfiltered>,NO,O,SO,N,S,NE,E,SE
    NO -> AttributeCreator_6
    O -> AttributeCreator_11
    SO -> AttributeCreator_12
    N -> AttributeCreator_13
    S -> AttributeCreator_14
    NE -> AttributeCreator_15
    E -> AttributeCreator_16
    SE -> AttributeCreator_17
AttributeCreator_6
    ATTR_TABLE = SET_TO NO = @Value(LIG_mi)
    -> Aggregator
AttributeCreator_11
    ATTR_TABLE = SET_TO O = @Value(LIG_mi)
    -> Aggregator
AttributeCreator_12
    ATTR_TABLE = SET_TO SO = @Value(LIG_mi)
    -> Aggregator
AttributeCreator_13
    ATTR_TABLE = SET_TO N = @Value(LIG_mi)
    -> Aggregator
AttributeCreator_14
    ATTR_TABLE = SET_TO S = @Value(LIG_mi)
    -> Aggregator
AttributeCreator_15
    ATTR_TABLE = SET_TO NE = @Value(LIG_mi)
    -> Aggregator
AttributeCreator_16
    ATTR_TABLE = SET_TO E = @Value(LIG_mi)
    -> Aggregator
AttributeCreator_17
    ATTR_TABLE = SET_TO SE = @Value(LIG_mi)
    -> Aggregator
Aggregator
    ACCUM_ATTRS_NAME = Merge Incoming Attributes
    AGGREGATE_TYPE = Homogeneous Collection (If Possible)
    GROUP_BY = mi
    MODE = Geometry - Assemble One Level
    SEP = ,
    AGGREGATE -> AttributeKeeper_2
AttributeKeeper_2
    KEEP_ATTRS = _escala,E,mi,N,NE,NO,O,S,SE,SO
    -> LIGACAO
    -> edicao (writer POSTGIS_2)
LIGACAO: Inspector
edicao (writer POSTGIS_2)
    attributes: id int8,PrimaryKey, mi varchar(80), bloco varchar(80), status varchar(80), editor varchar(80), inicioedicao varchar(80), terminoedicao varchar(80), revisor1 varchar(80), inicio1rev varchar(80), termino1rev varchar(80), servidor varchar(80), niveis varchar(200), densidade varchar(200), revisor2 varchar(80), inicio2rev varchar(80), termino2rev varchar(80), nome_carta varchar(80), inom text, iniciocorrecao1 varchar(80), terminocorrecao1 varchar(80), iniciocorrecao2 varchar(80), terminocorrecao2 varchar(80), impressa bool, ligacao bool, totalobj varchar(200), total_p numeric(20,0), total_l numeric(20,0), total_a numeric(20,0), txt_p numeric(20,0), txt_l varchar(200),
      o varchar(80), s varchar(80), se varchar(80), so varchar(80), l varchar(80), n varchar(80), no varchar(80), ne varchar(80), linha int2, coluna int2, regiao text

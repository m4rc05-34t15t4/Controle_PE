FME workspace numerar_linhaXcoluna.fmw

Parameters:
- SourceDataset_HTMLTABLE = $(FME_MF_DIR)projeto_bahia.html   # HTML Document
- SourceDataset_SHAPEFILE = $(FME_MF_DIR)lim_proj_bahia_p.shp   # Source Esri Shapefile(s)
- FEATURE_TYPES =
- SourceDataset_POSTGIS = Controle   # Database
- FEATURE_TYPES_2 = public.edicao

Readers:
- HTMLTABLE_1: HTMLTABLE from $(SourceDataset_HTMLTABLE)
- SHAPEFILE_1: SHAPEFILE from $(SourceDataset_SHAPEFILE)
- POSTGIS_1: POSTGIS from $(SourceDataset_POSTGIS)

limites_proj_bahia (reader SHAPEFILE_1)
    attributes: id number(20,0), mi char(254), bloco char(254), status char(254), editor char(254), inicioedic char(254), terminoedi char(254), revisor1 char(254), inicio1rev char(254), termino1re char(254), servidor char(254), niveis char(200), densidade char(200), revisor2 char(254), inicio2rev char(254), termino2re char(254), nome_carta char(254)
    -> Reprojector
    -> _All__2
_All__2: Inspector
Reprojector
    DEST = EPSG:31984
    INTERPOLATION_TYPE_NAME = Nearest Neighbor
    RASTER_CELL_SIZE = Preserve Cells
    RASTER_TOLERANCE = 0.0
    SOURCE = Read from feature
    REPROJECTED -> BoundingBoxAccumulator
BoundingBoxAccumulator
    ACCUM_ATTRS_NAME = Use Attributes From One Feature
    BOUNDING_BOX -> Tiler
Tiler
    BOUNDARY_CASES = No
    CLEANING_TOLERANCE = Automatic
    COL_ATTR = _column
    LINES_AS_SEGMENTS = No
    MEASURE_TYPE = Continuous
    MISSING_VAL_MODE = Compute
    NUM_HORIZONTAL_TILES = 75
    NUM_VERTICAL_TILES = 79
    ROW_ATTR = _row
    STARTINGCORNER = Upper Left
    TILING_TYPE = Number of Tiles
    TILED -> _All_
_All_: Inspector
edicao (reader POSTGIS_1)
    attributes: id int8,PrimaryKey, mi varchar(80), bloco varchar(80), status varchar(80), editor varchar(80), inicioedicao varchar(80), terminoedicao varchar(80), revisor1 varchar(80), inicio1rev varchar(80), termino1rev varchar(80), servidor varchar(80), niveis varchar(200), densidade varchar(200), revisor2 varchar(80), inicio2rev varchar(80), termino2rev varchar(80), nome_carta varchar(80)
    -> Reprojector_2
Reprojector_2
    DEST = EPSG:31984
    INTERPOLATION_TYPE_NAME = Nearest Neighbor
    RASTER_CELL_SIZE = Preserve Cells
    RASTER_TOLERANCE = 0.0
    SOURCE = Read from feature
    REPROJECTED -> Reprojector_2_Reprojected
Reprojector_2_Reprojected: Inspector
Table1 (reader HTMLTABLE_1) [off]
    attributes: Col1 text, Col2 text, Col3 text, Col4 text, Col5 text, Col6 text, Col7 text, Col8 text, Col9 text, Col10 text, Col11 text, Col12 text, Col13 text, Col14 text, Col15 text, Col16 text, Col17 text, Col18 text, Col19 text, Col20 text, Col21 text, Col22 text, Col23 text, Col24 text, Col25 text, Col26 text, Col27 text, Col28 text, Col29 text, Col30 text,
      Col31 text, Col32 text, Col33 text, Col34 text, Col35 text, Col36 text, Col37 text, Col38 text, Col39 text, Col40 text, Col41 text, Col42 text, Col43 text, Col44 text, Col45 text, Col46 text, Col47 text, Col48 text, Col49 text, Col50 text, Col51 text, Col52 text, Col53 text, Col54 text, Col55 text, Col56 text, Col57 text, Col58 text, Col59 text, Col60 text,
      Col61 text, Col62 text, Col63 text, Col64 text, Col65 text, Col66 text, Col67 text, Col68 text, Col69 text, Col70 text, Col71 text, Col72 text, Col73 text, Col74 text, Col75 text
    -> Table1
Table1: Inspector
